Attribute VB_Name = "CreateOVLayers"
Sub CreateOVLayers()
Dim i As Integer
Form.TreeView.Nodes.Clear
For i = 1 To 16
    Form.TreeView.Nodes.Add
Next i
    Form.TreeView.Nodes(1).Text = "ОВ_О_оборудование"
    Form.TreeView.Nodes(2).Text = "ОВ_О_труба"
    Form.TreeView.Nodes(3).Text = "ОВ_О_КИП"
    Form.TreeView.Nodes(4).Text = "ОВ_О_надпись"
    Form.TreeView.Nodes(5).Text = "ОВ_О_размер"
    Form.TreeView.Nodes(6).Text = "ОВ_В_оборудование"
    Form.TreeView.Nodes(7).Text = "ОВ_В_воздуховод"
    Form.TreeView.Nodes(8).Text = "ОВ_В_решетка"
    Form.TreeView.Nodes(9).Text = "ОВ_В_надпись"
    Form.TreeView.Nodes(10).Text = "ОВ_В_размер"
    Form.TreeView.Nodes(11).Text = "ОВ_экран"
    Form.TreeView.Nodes(12).Text = "ОВ_план"
    Form.TreeView.Nodes(13).Text = "ОВ_задание_АСО"
    Form.TreeView.Nodes(14).Text = "ОВ_задание_ЭТО"
    Form.TreeView.Nodes(15).Text = "ОВ_задание_ВК"
    Form.TreeView.Nodes(16).Text = "ОВ_задание_КТО"
    Form.Show
    ' Create a new layer
    Dim layerObj As AcadLayer
    If (Form.TreeView.Nodes(1).Checked = True) Then
        Set layerObj = ThisDrawing.Layers.Add("ОВ_О_оборудование")
       ' Assign the layer the color
    layerObj.Color = 51
    End If
    If (Form.TreeView.Nodes(2).Checked = True) Then
        Set layerObj = ThisDrawing.Layers.Add("ОВ_О_труба")
        layerObj.Color = 51
    End If
    If (Form.TreeView.Nodes(3).Checked = True) Then
        Set layerObj = ThisDrawing.Layers.Add("ОВ_О_КИП")
            layerObj.Color = 51
    End If
    If (Form.TreeView.Nodes(4).Checked = True) Then
        Set layerObj = ThisDrawing.Layers.Add("ОВ_О_надпись")
            layerObj.Color = acWhite
    End If
    If (Form.TreeView.Nodes(5).Checked = True) Then
        Set layerObj = ThisDrawing.Layers.Add("ОВ_О_размер")
            layerObj.Color = acWhite
    End If
    If (Form.TreeView.Nodes(6).Checked = True) Then
        Set layerObj = ThisDrawing.Layers.Add("ОВ_В_оборудование")
            layerObj.Color = 51
    End If
    If (Form.TreeView.Nodes(7).Checked = True) Then
        Set layerObj = ThisDrawing.Layers.Add("ОВ_В_воздуховод")
            layerObj.Color = 51
    End If
    If (Form.TreeView.Nodes(8).Checked = True) Then
        Set layerObj = ThisDrawing.Layers.Add("ОВ_В_решетка")
            layerObj.Color = 51
    End If
    If (Form.TreeView.Nodes(9).Checked = True) Then
        Set layerObj = ThisDrawing.Layers.Add("ОВ_В_надпись")
            layerObj.Color = acWhite
    End If
    If (Form.TreeView.Nodes(10).Checked = True) Then
        Set layerObj = ThisDrawing.Layers.Add("ОВ_В_размер")
            layerObj.Color = acWhite
    End If
    If (Form.TreeView.Nodes(11).Checked = True) Then
        Set layerObj = ThisDrawing.Layers.Add("ОВ_экран")
            layerObj.Color = acRed
    End If
    If (Form.TreeView.Nodes(12).Checked = True) Then
        Set layerObj = ThisDrawing.Layers.Add("ОВ_план")
            layerObj.Color = 254 'серый
    End If
    If (Form.TreeView.Nodes(13).Checked = True) Then
        Set layerObj = ThisDrawing.Layers.Add("ОВ_задание_АСО")
            layerObj.Color = acRed
    End If
    If (Form.TreeView.Nodes(14).Checked = True) Then
        Set layerObj = ThisDrawing.Layers.Add("ОВ_задание_ЭТО")
            layerObj.Color = acMagenta
    End If
    If (Form.TreeView.Nodes(15).Checked = True) Then
        Set layerObj = ThisDrawing.Layers.Add("ОВ_задание_ВК")
            layerObj.Color = acCyan
    End If
    If (Form.TreeView.Nodes(16).Checked = True) Then
        Set layerObj = ThisDrawing.Layers.Add("ОВ_задание_КТО")
            layerObj.Color = acGreen
    End If
End Sub

Attribute VB_Name = "Form"
Attribute VB_Base = "0{EADB9B4B-ABD0-4E58-A876-677CD4327080}{904D0A52-6C5A-4ABA-9310-0C118759B6AB}"
Attribute VB_GlobalNameSpace = False
Attribute VB_Creatable = False
Attribute VB_PredeclaredId = True
Attribute VB_Exposed = False
Attribute VB_TemplateDerived = False
Attribute VB_Customizable = False

Private Sub CommandButton_Click()
    Form.Hide
End Sub
